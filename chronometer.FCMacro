# -*- coding: utf-8 -*-
# (c) MaxiV, 2023

__Name__ = 'Chronometer_FreeCAD'
__Comment__ = 'A chronometer for FreeCAD'
__Author__ = 'Maxi Vasquez'
__Version__ = '0.2'
__Date__ = '2025-03-30'
__License__ = 'LGPL-2.0-or-later'

import PySide.QtCore as QtCore
import PySide.QtGui as QtGui
import PySide.QtWidgets as QtWidgets
import FreeCADGui as Gui

class TimerDialog(QtWidgets.QDialog):
    def __init__(self, parent=None):
        super(TimerDialog, self).__init__(parent)
        self.setWindowTitle("Chronometer")
        self.resize(200, 300)

        self.timer_label = QtWidgets.QLabel(self)
        self.timer_label.setAlignment(QtCore.Qt.AlignCenter)
        font = QtGui.QFont("Digital-7", 48, QtGui.QFont.Bold)  # Digital font
        self.timer_label.setFont(font)

        self.time_label = QtWidgets.QTextEdit(self)
        self.time_label.setReadOnly(True)
        self.time_label.setStyleSheet("font-size: 14px;")

        self.start_button = QtWidgets.QPushButton("Start", self)
        self.start_button.clicked.connect(self.start_stop_timer)

        self.next_button = QtWidgets.QPushButton("Next Part", self)
        self.next_button.clicked.connect(self.record_time)

        layout = QtWidgets.QVBoxLayout(self)
        layout.addWidget(self.timer_label)
        layout.addWidget(self.time_label)
        layout.addWidget(self.start_button)
        layout.addWidget(self.next_button)

        self.timer = QtCore.QTimer()
        self.timer.timeout.connect(self.update_timer)
        self.start_time = None
        self.is_running = False
        self.piece_counter = 1
        self.total_elapsed_time = 0
        self.last_piece_elapsed_time = 0

    def start_stop_timer(self):
        if self.is_running:
            self.timer.stop()
            self.is_running = False
            self.start_button.setText("Start")
            self.record_time()
        else:
            self.start_time = QtCore.QTime.currentTime()
            self.timer.start(100)  # 100 millisecond interval to display tenths of a second
            self.is_running = True
            self.start_button.setText("Stop")

    def record_time(self):
        if self.start_time is not None:
            current_time = QtCore.QTime.currentTime()
            elapsed_time = self.start_time.msecsTo(current_time) - self.last_piece_elapsed_time
            elapsed_minutes = elapsed_time // 60000
            elapsed_seconds = (elapsed_time // 1000) % 60
            elapsed_deciseconds = (elapsed_time // 100) % 10
            time_text = "Part {:02d}: {:02d}:{:02d}.{:01d}".format(
                self.piece_counter, elapsed_minutes, elapsed_seconds, elapsed_deciseconds)
            self.time_label.append(time_text)
            self.last_piece_elapsed_time = self.start_time.msecsTo(current_time) - self.total_elapsed_time
            self.piece_counter += 1

    def update_timer(self):
        current_time = QtCore.QTime.currentTime()
        elapsed_time = self.start_time.msecsTo(current_time) - self.total_elapsed_time
        elapsed_minutes = elapsed_time // 60000
        elapsed_seconds = (elapsed_time // 1000) % 60
        elapsed_deciseconds = (elapsed_time // 100) % 10
        self.timer_label.setText("{:02d}:{:02d}.{:01d}".format(
            elapsed_minutes, elapsed_seconds, elapsed_deciseconds))

    def closeEvent(self, event):
        if self.is_running:
            self.start_stop_timer()
        event.accept()

timer_dialog = TimerDialog()
timer_dialog.show()
